# SPDX-FileCopyrightText: 2026 ishikawa-slfecd  [slfecd (ishikawa-slfecd)](https://github.com/slfecd)
# SPDX-License-Identifier: LGPL-2.1-or-later OR Apache-2.0

# AI生成物を元に改変しています
# - ワースト・トレラントの各要素（頂点、エッジ、面）を探す
#   - FreeCADのトレランス初期値を超える要素を選択状態にする（選択色に変化）
#   - レポートビューに結果表示
# - データム頂点の追加オプション：頂点を選択しても色変化しない事があるため
# - バージョン情報などは package.xml を参照してね
#
# - FreeCAD v1.1.1 : Python v3.11.14
# - Windows10 64bit


# ruff: noqa: I001
from typing import Final, TypeAlias, cast
from dataclasses import dataclass

import os
import re  # 正規表現
import xml.etree.ElementTree as ET

import FreeCAD as App
import FreeCADGui as Gui
import Part  # FreeCAD ワークベンチ

__date__: Final[str] = "2026-08-13"  # YMD

MACRO_NAME: Final[str] = "FindWorstTolerance"
FLAG_SAME_WORST_TOLERANCE_MODE: Final[bool] = True  # 同値ワースト要素を全探索
FLAG_ADD_DATUM_POINT: Final[bool] = False  # True=データム点を追加

Type_SubShape: TypeAlias = Part.Vertex | Part.Edge | Part.Face


@dataclass
class ShapeElement:
    # Memo :
    #   - Document.Feature.Shape.(element)
    #   - Feature.Document
    feature_obj: Part.Feature  # Body, Sketch, AdditivePipe, Boolean, Fillet, etc...
    element: Type_SubShape


def collect_element(obj: Part.Feature) -> list[ShapeElement] | None:
    """Vertex, Edge, Face 要素を取得して返す"""

    if (not hasattr(obj, "Shape")) or obj.Shape.isNull():
        return None

    shape: Final = cast(Part.Shape, obj.Shape)

    all_raw_elements: Final = cast(
        Type_SubShape, [*shape.Vertexes, *shape.Edges, *shape.Faces]
    )
    element_list: list[ShapeElement] = [
        ShapeElement(element=cast(Type_SubShape, el), feature_obj=obj)
        for el in all_raw_elements  # pyright: ignore[reportUnknownVariableType]
    ]

    return element_list if element_list else None


def get_element_name(se: ShapeElement) -> str:
    """要素から Vertex1 Edge2 Face3 のような名前を返す"""

    assert hasattr(se.feature_obj, "Shape"), (
        "ShapeElement.feature_obj requires a Shape object. （ShapeElement.feature_obj に Shapeオブジェクトが必要です）"
    )

    (element_type_name, element_index) = cast(
        tuple[str | None, int],
        se.feature_obj.Shape.findSubShape(se.element),  # type: ignore[attr-defined]  # freecad-stubs-1.0.21 に定義なし
    )

    # if element_type_name is None:
    #     App.Console.PrintLog(
    #         f"Shape.findSubShape() return is None. Feature:{se.feature_obj.Label}({se.feature_obj.Name}) , ShapeType:{se.feature_obj.Shape.ShapeType}\n"
    #     )

    return (
        f"{element_type_name}{element_index}" if element_type_name is not None else ""
    )


def find_worst_tolerance(obj: Part.Feature) -> list[ShapeElement] | None:
    """Vertex, Edge, Face 各要素毎のワーストトレランスを返す"""

    worst_element_list: list[ShapeElement] = []  # 戻り値

    STR_ELEMENT_NOT_FOUND: Final[str] = (
        "No valid elements found. （有効な要素が見つかりません）\n"
    )

    # トレランス閾値（FreeCAD設定値）取得：超えたら要素選択
    TOLERANCE_TH: Final = cast(float, Part.Precision.confusion())  # type: ignore
    assert TOLERANCE_TH == 1e-7, (
        f"FreeCAD returned Part.Precision.confusion() != 1E-7 : {TOLERANCE_TH:G}"
    )

    App.Console.PrintMessage(
        f"=== Worst tolerance （トレランス ワースト）: {obj.Label} ({obj.FullName})\n"
    )

    element_list: Final = collect_element(obj)
    if not element_list:
        App.Console.PrintMessage(STR_ELEMENT_NOT_FOUND)  # 要素なし
        return None

    @dataclass
    class TargetElement:
        prefix: str
        obj_class: type[Type_SubShape]

    target_definitions: Final[list[TargetElement]] = [
        TargetElement("[Vertex] ", Part.Vertex),
        TargetElement("[Edge]   ", Part.Edge),
        TargetElement("[Face]   ", Part.Face),
    ]

    for target in target_definitions:
        prefix = target.prefix
        # 要素抽出
        filter_element_list = [
            item for item in element_list if isinstance(item.element, target.obj_class)
        ]
        if not filter_element_list:
            App.Console.PrintMessage(f"{prefix}{STR_ELEMENT_NOT_FOUND}")  # 要素なし
            continue

        if FLAG_SAME_WORST_TOLERANCE_MODE:
            # 同値ワースト複数要素に対応
            worst_tolerance = cast(
                float,
                max(
                    filter_element_list,
                    key=lambda item: cast(float, item.element.Tolerance),
                ).element.Tolerance,
            )
            worst_shape_list = [
                item
                for item in filter_element_list
                if item.element.Tolerance >= worst_tolerance
            ]

            # 結果表示（レポートビュー）
            flag_over_tolerance: bool = TOLERANCE_TH < worst_tolerance
            for worst_shape in worst_shape_list:
                element_tol = cast(float, worst_shape.element.Tolerance)
                element_name = get_element_name(worst_shape)
                App.Console.PrintMessage(
                    f"{prefix}Worst Tolerance: {element_tol} mm ({element_name})\n"
                )
                if not flag_over_tolerance:
                    break

            if flag_over_tolerance:
                worst_element_list.extend(worst_shape_list)
        else:
            # 挙動変更前のコード：最初に見つけたワースト要素のみ取得
            worst_shape = max(
                filter_element_list,
                key=lambda item: cast(float, item.element.Tolerance),
            )

            # 結果表示（レポートビュー）
            element_tol = cast(float, worst_shape.element.Tolerance)
            element_name = get_element_name(worst_shape)
            App.Console.PrintMessage(
                f"{prefix}Worst Tolerance: {element_tol:G} mm ({element_name})\n"
            )

            if TOLERANCE_TH < element_tol:
                worst_element_list.append(worst_shape)
        # if FLAG_SAME_WORST_TOLERANCE_MODE

    # for target

    App.Console.PrintMessage("===\n")

    return worst_element_list if worst_element_list else None


def element_add_selection(
    element_list: list[ShapeElement], flagAddDatumPoint: bool = False
) -> None:
    """引数で指定された要素を選択状態にする"""

    TYPEID_DATUM_POINT: Final = "Part::DatumPoint"

    for item in element_list:
        obj = item.feature_obj
        element = cast(Type_SubShape, item.element)  # リンター警告バグ？
        element_name = get_element_name(item)
        Gui.Selection.addSelection(obj.Document.Name, obj.Name, element_name)

        if flagAddDatumPoint and isinstance(element, Part.Vertex):
            # FreeCAD1.1.1 たぶんバグの対策：選択した頂点が選択色に変化しない
            # データム点を追加する
            datumPointLabel = f"__WorstVtx_{obj.Label}"
            doc = obj.Document

            # 旧データム点を削除
            obj_list = cast(list[Part.Feature], doc.getObjectsByLabel(datumPointLabel))
            obj_dp_list = [
                item for item in obj_list if item.TypeId == TYPEID_DATUM_POINT
            ]
            for obj_dp in obj_dp_list:
                doc.removeObject(obj_dp.Name)

            # データム点追加
            d_point = cast(
                App.GeoFeature,
                doc.addObject(TYPEID_DATUM_POINT),  # エラー時は例外発生
            )
            d_point.Label = datumPointLabel
            d_point.Label2 = f"({element_name}) Tolerance {element.Tolerance:g}"
            d_point.MapMode = "Deactivated"  # type: ignore[attr-defined]  # アタッチ無し(初期値)
            d_point.Placement.Base = cast(App.Vector, element.Point)

            # データム点選択
            Gui.Selection.addSelection(doc.Name, d_point.Name)

    # return


# main
def main() -> None:
    # 選択オブジェクトを取得
    check_objects: Final[list[Part.Feature]] = Gui.Selection.getSelection("*")
    if not check_objects:
        App.Console.PrintWarning(
            "Select an object in the model tree first. （モデルツリーでオブジェクトを選択してから実行してください）\n"
        )
        return

    # ワースト要素検索
    worst_element_list: list[ShapeElement] = []
    for obj in check_objects:
        element_list = find_worst_tolerance(obj)
        if element_list:
            worst_element_list.extend(element_list)
    # for

    # ワースト要素を選択状態にする
    if worst_element_list:
        Gui.Selection.clearSelection()
        element_add_selection(worst_element_list, FLAG_ADD_DATUM_POINT)
        # if FLAG_ADD_DATUM_POINT:
        #     obj.recompute()

    Gui.updateGui()
    return


@dataclass
class PackageMeta:
    name: str = ""
    version: str = ""
    macro_name: str = ""


def get_package_meta(xml_filename: str = "package.xml") -> PackageMeta | None:
    """
    パッケージ名、バージョン番号、マクロ名を取得
    - package.xmlファイルからメタ情報を取得
    - https://wiki.freecad.org/Package_Metadata
    """

    # アドオンマネージャーのインストーラーがzip展開するディレクトリ
    xml_path: Final = os.path.join(
        App.getUserAppDataDir(), "Mod", MACRO_NAME, xml_filename
    )
    if not os.path.exists(xml_path):
        return None  # Error

    try:
        with open(xml_path, "r", encoding="utf-8") as f:
            xml_data: Final = f.read()

        # 名前空間 xmlns="..." の記述を削除する
        xml_data_clean: Final = re.sub(r'\sxmlns="[^"]+"', "", xml_data, count=1)
        root: Final = ET.fromstring(xml_data_clean)

    except (ET.ParseError, PermissionError, KeyError) as e:
        App.Console.PrintError(f"XML Parse Error: {e}\n")
        return None

    if "package" != root.tag:
        return None  # Error

    def get_meta_text(tag_name: str, default_value: str = "") -> str:
        if (elm := root.find(tag_name)) is None:
            return default_value
        if (text := elm.text) is None:
            return default_value

        return text.strip()

    # メタ取得
    meta: PackageMeta = PackageMeta()
    meta.name = get_meta_text("name", MACRO_NAME)
    meta.version = get_meta_text("version", "0.0.0")
    meta.macro_name = get_meta_text("./content/macro/name", MACRO_NAME)

    return meta


# マクロの実行
if __name__ == "__main__":
    if (meta := get_package_meta()) is None:
        App.Console.PrintLog("Failed to load package.xml （package.xml読み込み失敗）\n")
        meta = PackageMeta(macro_name=MACRO_NAME, version="0.0.0")

    App.Console.PrintMessage(f"*** START: {meta.macro_name} v{meta.version}\n")
    main()
    App.Console.PrintMessage("*** END\n")
