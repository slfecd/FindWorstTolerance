# AI生成物を元に改変しています
# - トレラントのワースト１の各要素（頂点、エッジ、面）を探す
# - FreeCADのトレランス初期値を超える要素を選択（選択色になる）
#   - なんか頂点選択しても色変化しないので、データム頂点を追加してみた
# - レポートビューにも情報表示
#
# - FreeCAD Ver1.1.1 マクロ(.FCMacro)
# - Windows10 64bit

from typing import Final, TypeAlias, cast
from dataclasses import dataclass

# 実行中マクロのファイル名取得に使用
import os
import inspect

# FreeCAD
import FreeCAD as App
import FreeCADGui as Gui
import Part  # ワークベンチ


FLAG_ADD_DATUM_POINT: Final[bool] = True  # データム点を追加


Ttyp_SubShape: TypeAlias = Part.Vertex | Part.Edge | Part.Face


@dataclass
class ShapeElement:
    # Memo :
    #   - Document.Feature.Shape.(element)
    #   - Feature.Document
    feature_obj: Part.Feature  # Body, Sketch, AdditivePipe, Boolean, Fillet, etc...
    element: Ttyp_SubShape


def collect_element(obj: Part.Feature) -> list[ShapeElement] | None:
    """Vertex, Edge, Face 要素を取得して返す"""

    if (not hasattr(obj, "Shape")) or obj.Shape.isNull():
        return None

    shape: Final = cast(Part.Shape, obj.Shape)

    all_raw_elements: Final = cast(
        Ttyp_SubShape, [*shape.Vertexes, *shape.Edges, *shape.Faces]
    )
    element_list: list[ShapeElement] = [
        ShapeElement(element=cast(Ttyp_SubShape, el), feature_obj=obj)
        for el in all_raw_elements  # pyright: ignore[reportUnknownVariableType]
    ]

    return element_list if element_list else None


def get_element_name(se: ShapeElement) -> str:
    """要素から Vertex1 Edge2 Face3 のような名前を返す"""

    assert hasattr(se.feature_obj, "Shape"), (
        "ShapeElement.feature_obj に Shapeオブジェクトが必要です"
    )

    (element_type_name, element_index) = cast(
        tuple[str | None, int],
        se.feature_obj.Shape.findSubShape(se.element),  # type: ignore[attr-defined]  # freecad-stubs (1.0.21) に定義なし
    )

    assert element_type_name is not None, (
        "FreeCAD returned None for subshape type name."
    )

    return f"{element_type_name}{element_index}"


def find_worst_tolerance(obj: Part.Feature) -> list[ShapeElement] | None:
    """Vertex, Edge, Face 各要素毎のワーストトレランスを返す"""

    worst_element_list: list[ShapeElement] = []  # 戻り値

    STR_ELEMENT_NOT_FOUND: Final[str] = "有効な要否が見つかりませんでした。\n"

    # トレランス閾値（FreeCAD設定値）取得：超えたら要素選択
    TOLERANCE_TH: Final = cast(float, Part.Precision.confusion())  # type: ignore
    assert TOLERANCE_TH == 1e-7, (
        f"FreeCAD returned Part.Precision.confusion() != 1E-7 : {TOLERANCE_TH:G}"
    )

    App.Console.PrintMessage(f"=== トレランス ワースト: {obj.Label} ({obj.Name})\n")

    element_list: Final = collect_element(obj)
    if not element_list:
        App.Console.PrintMessage(STR_ELEMENT_NOT_FOUND)  # 要素なし
        return None

    @dataclass
    class TargetElement:
        prefix: str
        obj_class: type[Ttyp_SubShape]

    target_definitions: Final[list[TargetElement]] = [
        TargetElement("[Vertex] ", Part.Vertex),
        TargetElement("[Edge]   ", Part.Edge),
        TargetElement("[Face]   ", Part.Face),
    ]

    for target in target_definitions:
        prefix = target.prefix
        # 要素抽出
        filter_element_list = [
            item for item in element_list if isinstance(item.element, target.obj_class)
        ]
        if not filter_element_list:
            App.Console.PrintMessage(f"{prefix}{STR_ELEMENT_NOT_FOUND}")  # 要素なし
            continue

        worst_shape = max(filter_element_list, key=lambda item: item.element.Tolerance)

        # 結果表示（レポートビュー）
        element_tol = cast(float, worst_shape.element.Tolerance)
        element_name = get_element_name(worst_shape)
        App.Console.PrintMessage(
            f"{prefix}Worst Tolerance: {element_tol:G} mm ({element_name})\n"
        )

        if TOLERANCE_TH < element_tol:
            worst_element_list.append(worst_shape)
    # for target

    App.Console.PrintMessage("===\n")

    return worst_element_list if worst_element_list else None


def element_add_selection(
    element_list: list[ShapeElement], flagAddDatumPoint: bool = False
) -> None:
    """引数で指定された要素を選択状態にする"""

    TYPEID_DATUM_POINT: Final = "Part::DatumPoint"

    for item in element_list:
        obj = item.feature_obj
        element = cast(Ttyp_SubShape, item.element)  # リンター警告バグ？
        element_name = get_element_name(item)
        Gui.Selection.addSelection(obj.Document.Name, obj.Name, element_name)

        if flagAddDatumPoint and isinstance(element, Part.Vertex):
            # FreeCAD1.1.1 たぶんバグの対策：選択した頂点が選択色に変化しない
            # データム点を追加する
            datumPointLabel = f"__WorstVtx_{obj.Label}"
            doc = obj.Document

            # 旧データム点を削除
            obj_list = cast(list[Part.Feature], doc.getObjectsByLabel(datumPointLabel))
            obj_dp_list = [
                item for item in obj_list if item.TypeId == TYPEID_DATUM_POINT
            ]
            for obj_dp in obj_dp_list:
                doc.removeObject(obj_dp.Name)

            # データム点追加
            d_point = cast(
                App.GeoFeature,
                doc.addObject(TYPEID_DATUM_POINT),  # エラー時は例外発生
            )
            d_point.Label = datumPointLabel
            d_point.Label2 = f"({element_name}) Tolerance {element.Tolerance:g}"
            d_point.MapMode = "Deactivated"  # type: ignore[attr-defined]  # アタッチ無し(初期値)
            d_point.Placement.Base = cast(App.Vector, element.Point)

            # データム点選択
            Gui.Selection.addSelection(doc.Name, d_point.Name)

    return


# main
def main() -> None:
    # 選択オブジェクトを取得
    check_objects: Final[list[Part.Feature]] = Gui.Selection.getSelection()
    if not check_objects:
        App.Console.PrintWarning(
            "オブジェクトが選択されていません。モデルツリーでオブジェクトを選択してから実行してください。\n"
        )
        return

    # ワースト要素検索
    worst_element_list: list[ShapeElement] = []
    for obj in check_objects:
        # if (obj is None) or (not hasattr(obj, "Shape")) or obj.Shape.isNull():
        #     continue

        element_list = find_worst_tolerance(obj)
        if element_list:
            worst_element_list.extend(element_list)
    # for

    # ワースト要素を選択状態にする
    if worst_element_list:
        Gui.Selection.clearSelection()
        element_add_selection(worst_element_list, FLAG_ADD_DATUM_POINT)
        # if FLAG_ADD_DATUM_POINT:
        #     obj.recompute()

    Gui.updateGui()
    return


# マクロの実行
if __name__ == "__main__":
    # 実行中マクロのファイル名を取得表示
    name: str = "Macro"
    try:
        frame: Final = inspect.currentframe()
        if frame:
            script_path: Final = inspect.getframeinfo(frame).filename
            name = os.path.basename(script_path)
    except Exception:
        pass

    #
    App.Console.PrintMessage(f"*** START: {name}\n")
    main()
    App.Console.PrintMessage("*** END\n")
